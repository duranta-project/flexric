--/*
-- * SPDX-License-Identifier: LicenseRef-CSSL-1.0
-- */



-- ASN1 START
-- **************************************************************
-- E2SM-PDCP Stats
-- Information Element Definitions
-- 
-- **************************************************************

E2SM-PDCPStats-IEs { }

DEFINITIONS AUTOMATIC TAGS ::= 

BEGIN

-- **************************************************************
--
-- Lists
--
-- **************************************************************

maxofRANParameters						INTEGER ::= 255

-- E2 Service model IEs

-- ---------------------------------------------------
-- Event Trigger Definition OCTET STRING contents
-- ---------------------------------------------------

-- E2SM-PDCPStats-EventTriggerDefinition IE
E2SM-PDCPStats-EventTriggerDefinition ::= CHOICE{
	eventDefinition-Format1		E2SM-PDCPStats-EventTriggerDefinition-Format1,
	...
}

-- E2SM-PDCPStats-eventTriggerDefinition IE Format 1
E2SM-PDCPStats-EventTriggerDefinition-Format1 ::= SEQUENCE{
	triggerNature						PDCPStats-TriggerNature,
	...
}

-- ---------------------------------------------------
-- Action Definition OCTET STRING contents
-- ---------------------------------------------------

E2SM-PDCPStats-ActionDefinition ::= CHOICE{
	actionDefinition-Format1		E2SM-PDCPStats-ActionDefinition-Format1,
	...
}

-- E2SM-PDCPStats-actionDefinition IE used for Action Format 1
E2SM-PDCPStats-ActionDefinition-Format1 ::= SEQUENCE{
	ranParameter-List					SEQUENCE (SIZE(1..maxofRANParameters)) OF RANparameter-Item OPTIONAL,
	...
}



-- ---------------------------------------------------
-- Indication Header OCTET STRING contents
-- ---------------------------------------------------

E2SM-PDCPStats-IndicationHeader ::= CHOICE{
	indicationHeader-Format1		E2SM-PDCPStats-IndicationHeader-Format1,
	...
}

-- E2SM-PDCPStats-indicationHeader Format 1
E2SM-PDCPStats-IndicationHeader-Format1 ::= SEQUENCE{
	indicationHeaderParam						PDCPStats-Header,
	...
}

-- ---------------------------------------------------
-- Indication Message OCTET STRING contents
-- ---------------------------------------------------

-- E2SM-PDCPStats-indicationMessage IE
E2SM-PDCPStats-IndicationMessage ::= CHOICE{
	indicationMessage-Format1		E2SM-PDCPStats-IndicationMessage-Format1,
	...
}

-- E2SM-PDCPStats-IndicationMessage Format 1
E2SM-PDCPStats-IndicationMessage-Format1 ::= SEQUENCE{
        indicationMsgParam                      PDCPStats-Message,
        ...
}


-- ---------------------------------------------------
-- Call Process ID
-- ---------------------------------------------------

-- Not defined in this E2SM

-- ---------------------------------------------------
-- Control Header OCTET STRING contents
-- ---------------------------------------------------

-- E2SM-PDCPStats-ControlHeader
E2SM-PDCPStats-ControlHeader ::= CHOICE{
	controlHeader-Format1		E2SM-PDCPStats-ControlHeader-Format1,
	...
}

-- E2SM-PDCPStats-ControlHeader Format 1
E2SM-PDCPStats-ControlHeader-Format1 ::= SEQUENCE{
	controlHeaderParam			PDCPStats-Header,
	...
}


-- ---------------------------------------------------
-- Control Message OCTET STRING contents
-- ---------------------------------------------------

-- E2SM-PDCPStats-ControlMessage
E2SM-PDCPStats-ControlMessage ::= CHOICE{
	controlMessage-Format1		E2SM-PDCPStats-ControlMessage-Format1,
	...
}

-- E2SM-PDCPStats-controlMessage Format 1
E2SM-PDCPStats-ControlMessage-Format1 ::= SEQUENCE{
	controlMsgParam				PDCPStats-Message,
	...
}

-- ---------------------------------------------------
-- Control Outcome OCTET STRING contents
-- ---------------------------------------------------

-- Not defined in this E2SM



-- ---------------------------------------------------
-- RAN Function definition OCTET STRING contents
-- ---------------------------------------------------

-- Not defined in this E2SM




-- ---------------------------------------------------
-- commmon IEs
-- ---------------------------------------------------

-- A
-- B
-- C
-- D
-- E
-- F
-- G
-- H

PDCPStats-Header ::= INTEGER

PDCPStats-Message ::= OCTET STRING

PDCPStats-TriggerNature ::= ENUMERATED{
	oneMs,
	twoMs,
	fiveMs,
	...
}
-- I
-- J
-- K
-- L
-- M
-- N
-- O
-- P
-- Q
-- R


RANparameter-Item ::= SEQUENCE {
	ranParameter-ID			RANparameter-ID,
	ranParameter-Name		RANparameter-Name,
	ranParameter-Test		RANparameter-Test,
	ranParameter-Value		RANparameter-Value,
	...
}


RANparameter-ID ::= INTEGER (0..maxofRANParameters)

RANparameter-Name ::= OCTET STRING

RANparameter-Test ::= ENUMERATED{
	equal,
	greaterthan,
	lessthan,
	contains,
	present,
	...
}

RANparameter-Value ::= OCTET STRING

-- S
-- T
-- U
-- V
-- W
-- X
-- Y
-- Z

END
-- ASN1STOP
